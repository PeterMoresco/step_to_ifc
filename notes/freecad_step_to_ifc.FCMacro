'''
This is a macro to transform the selected STEP obj to a IFC,
with the same tree structure and geometries.
'''
# TODO Change the name of the original object before the new
# TODO Change the IFC type
# TODO Add the headless functionality
# TODO Checks the properties for the IFC


from tempfile import NamedTemporaryFile
import os
import tempfile


def add_children(obj, container):
    # Get the children
    children = obj.OutList
    for child in children:
        # Check the type
        if child.TypeId == 'App::Part':  # Assembly
            # Create the container
            subCont = make_b_part(child)
            # Adds the child to the dad
            container.addObject(subCont)
            if len(child.OutList) != 0:
                add_children(child, subCont)
        elif child.TypeId == 'Part::Feature':  # Part/Component
            # Make the component
            component = make_component(child)
            # Adds to its parent
            # COMM
            print('Adding {} to {}'.format(
                component.Label, container.Label))
            container.addObject(component)


def make_component(item):
    # Create the component
    component = Arch.makeComponent(item)
    # Change the label
    component.Label = item.Label
    # Change the placement
    component.Placement = item.getGlobalPlacement()
    return component


def make_b_part(item):
    # Create the container
    container = Arch.makeBuildingPart()
    # Copy the placement
    container.Placement = item.Placement.copy()
    # Copy the label
    container.Label = item.Label
    return container


def step_to_ifc(obj):
    # Import the Arch lybrary
    import Arch
    # Create the main container
    cont = make_b_part(obj)
    # Add the children to the tree of the dad
    add_children(obj, cont)
    return cont


def select_bigger_container():
    # Get all the container objects in the tree
    containers = list(filter(lambda x: x.TypeId ==
                      'App::Part', FreeCAD.ActiveDocument.Objects))
    # Gets the children count
    childrenCount = [len(x.OutListRecursive) for x in containers]
    # Sort them
    sortedList = [x for _, x in sorted(
        zip(childrenCount, containers), key=lambda duo: duo[0])]
    # The main container
    return sortedList[-1]


def import_step(filePath, nDocName):
    # Check filepath
    import os.path
    if not os.path.exists(filePath):
        raise Exception('Filepath {} invalid.'.format(filePath))
    import ImportGui
    ImportGui.insert(filePath, nDocName)


def export_ifc(obj, filePath):
    # Create the list to hold the objects
    __objs__ = []
    # Collect the items
    __objs__.append(FreeCAD.ActiveDocument.getObject(obj.Name))
    # Export the item
    import exportIFC
    exportIFC.export(__objs__, filePath)


# Initiates a new document
newDocName = 'TempPart'
App.newDocument(newDocName)
# The document must been save before in order
# To do not open the saveas popup
tempFile = NamedTemporaryFile(suffix='.FCStd', delete=True)
tempname = tempFile.name
App.getDocument(newDocName).saveAs(tempname)
# Activate the workbench
Gui.activateWorkbench("ArchWorkbench")
# Import step file
stepPath = 'C:\\Users\\pedro\\Documents\\step_to_ifc\\test_models\\rm6067_300_2_slide_base_r3_asm.stp'
import_step(stepPath, newDocName)
# Gets the object
obj = select_bigger_container()
# Creates the IFC object
ifcContainer = step_to_ifc(obj)
# Export the IFC
fPath = r'C:\\Users\\pedro\\Documents\\step_to_ifc\\test_models\\model.ifc'
export_ifc(ifcContainer, fPath)
# Close the document
App.closeDocument(newDocName)
